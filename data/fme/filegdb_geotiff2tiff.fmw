FME workspace filegdb_geotiff2tiff.fmw

Parameters:
- SourceDataset_FILEGDB = $(FME_MF_DIR)Selected.gdb   # File Geodatabase
- DestDataset_TIFF = $(FME_MF_DIR)train_data   # Destination TIFF (Tagged Image File Format) Folder
- SourceDataset_GEOTIFF = ""$(FME_MF_DIR)影像数据\TIF\LPX_Resample.img.tif" "$(FME_MF_DIR)影像数据\TIF\XFX_Resample.img.tif" "$(FME_MF_DIR)影像数据\TIF\YCQ_Resample.img.tif""   # Source GeoTIFF File(s)
- FEATURE_TYPES =

Readers:
- FILEGDB_1: FILEGDB from $(SourceDataset_FILEGDB)
- GEOTIFF_1: GEOTIFF from $(SourceDataset_GEOTIFF)

Writers:
- TIFF_1: TIFF to $(DestDataset_TIFF)

GEOTIFF (reader GEOTIFF_1)
    attributes: datatype char(255)
    -> Clipper [CLIPPEE]
UV_LCRA2 (reader FILEGDB_1)
    attributes: OBJECTID objectid, CC text(8), Tag smallint, Feature text(64), ElemSTime text(8), ElemETime text(8), AreaCode int, FEATID text(16), ChangeType smallint, Shape_Length double, Shape_Area double, Classcode text(20), Classvalue int, Classname text(20), RED int, GREEN int, BLUE int, Count int
    -> Reprojector
Reprojector
    DEST = EPSG:4509
    INTERPOLATION_TYPE_NAME = Nearest Neighbor
    RASTER_CELL_SIZE = Preserve Cells
    RASTER_TOLERANCE = 0.0
    SOURCE = Read from feature
    REPROJECTED -> BoundingBoxReplacer
    REPROJECTED -> Clipper [CLIPPER]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> GEOTIFF (writer TIFF_1)
GEOTIFF (writer TIFF_1)
BoundingBoxReplacer [off]
    BOXTYPE = 2D Bounding Box
